BasicModule DEFINITIONS AUTOMATIC TAGS ::= BEGIN

Number          ::= INTEGER (-100000000000000000..100000000000000000)
Version         ::= INTEGER
Int             ::= INTEGER
ASNBoolean      ::= BOOLEAN
Hash            ::= OCTET STRING (SIZE(1..64))
Key             ::= OCTET STRING (SIZE(1..256))
Signature       ::= OCTET STRING
BerEncoding     ::= OCTET STRING
EncryptedData   ::= OCTET STRING
BinaryData      ::= OCTET STRING

Status ::= ENUMERATED {
    init    (0),
    debit   (1),
    processing   (2),
    waiting   (3),
    credit  (4),
    complete (5),
    nested      (6)
    
}


END
