AccountModule DEFINITIONS AUTOMATIC TAGS ::= BEGIN
    IMPORTS Version, Hash, Key, Number
        FROM BasicModule
        Role
        FROM SecurityModule
        PrivateKey
        FROM PrivateKeyModule;


AccountType ::= ENUMERATED {
    individual,
    organisation,
    proxy,
    blockChain
}

Account ::= SEQUENCE {
    version                 Version,
    -- hash of public key
    id                      Hash,
    name                    UTF8String,
    publicKey               Key,
    accountType             AccountType,
    accountInfo             SEQUENCE OF ANY,
    role                    SEQUENCE OF Hash,
    permissions             SEQUENCE OF Hash
}

AccountLink ::= SEQUENCE {
    version         Version,
    id              Hash,
    name            UTF8String,
    linkKey         PrivateKey,
    linkId          Hash
}

AccountBlockChain ::= SEQUENCE {
    version         Version,
    id              Hash,
    name            UTF8String,
    private         BOOLEAN,
    blockId         Hash,
    blockKey        PrivateKey
}

AccountBalance ::= SEQUENCE {
    version         Version,
    lastTransaction Hash,
    balance         Number
}

END
