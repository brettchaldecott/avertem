BlockChainModule DEFINITIONS AUTOMATIC TAGS ::= BEGIN
    IMPORTS Number, Hash, Version, Signature
        FROM BasicModule
        Account 
        FROM AccountModule
        Action
        FROM ActionModule
        SoftwareConsensus
        FROM SofwareConsensusModule
        Transaction, SignedTransaction, ChangeSet, SignedChangeSet, TransactionWrapper
        FROM TransactionModule;


Block ::= SEQUENCE {
    version             Version,
    date                UTCTime,
    parent              Hash,
    transactions        SEQUENCE OF TransactionWrapper,
    acceptedCheck       SoftwareConsensus,
    validateCheck       SoftwareConsensus,
    merkelRoot          Hash
}

SignedBlock ::= SEQUENCE {
    version         Version,
    date            UTCTime,
    parent          Hash,
    block           Block,
    hash            Hash,
    signatures      SEQUENCE OF Signature
}

END
