TransactionModule DEFINITIONS AUTOMATIC TAGS ::= BEGIN
    IMPORTS Number, Hash, Version, Key, Signature, Status, EncryptedData, ASNBoolean, Int
        FROM BasicModule
        Action
        FROM ActionModule
        ChangeSet, SignedTransaction
        FROM ChangeSetModule;

Transaction ::= SEQUENCE {
    version         Version,
    date            UTCTime,
    value           Number,
    parent          Hash,
    encrypted       ASNBoolean,
    -- the source account for the transaction
    sourceAccount   Hash,
    -- the target account for the transaction
    targetAccount   Hash,
    -- the transaction signator and creator id are there
    -- to track internal transactions for security and validation purposes
    transactionSignator Hash,
    creatorId       Hash,
    actions         SEQUENCE OF Action
}

SignedTransaction ::= SEQUENCE {
    version         Version,
    transaction     Transaction,
    transactionHash Hash,
    signature       Signature
}

TransactionTrace ::= SEQUENCE {
    traceHash       Hash,
    signature       Signature,
    signatureHash   Hash
}

TransactionWrapper ::= SEQUENCE {
    version             Version,
    -- transaction header information
    sourceAccount       Hash,
    targetAccount       Hash,
    parent              Hash,
    feeAccount          Hash,
    transactionHash     Hash,
    signature           Signature,
    -- transaction 
    signedTransaction   SignedTransaction,
    transactionTrace    SEQUENCE OF TransactionTrace,
    -- status and changeset
    currentStatus       Status,
    changeSet           SEQUENCE OF SignedChangeSet
}

EncryptedDataWrapper ::= SEQUENCE {
    version         Version,
    transaction     EncryptedData,
    -- the hash of the transaction when encrypted
    -- this is here to validate that the onion encryption is being
    -- decrypted correctly through the various layers.
    hash            SEQUENCE OF Hash
}


TransactionMessage ::= SEQUENCE {
    version              Version,
    -- transaction header information
    transaction          TransactionWrapper,
    availableTime        Int,
    elapsedTime          Int,
    sideTransactions     SEQUENCE OF TransactionMessage,
    encryptedSideTransactions  SEQUENCE OF EncryptedDataWrapper

    -- nestedTransactions   SEQUENCE OF CHOICE {
        --sideTransaction  TransactionMessage,
        -- the data that is encrypted this will be an encrypted transaction message
        --encryptedSideTransaction    EncryptedDataWrapper
    -- }
}




END
