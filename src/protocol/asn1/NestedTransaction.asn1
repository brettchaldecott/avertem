NestedTransactionModule DEFINITIONS AUTOMATIC TAGS ::= BEGIN
    IMPORTS Number, EncryptedData, Hash
        FROM BasicModule
        SignedTransaction, Transaction
        FROM TransactionModule;

--TransactionData ::= CHOICE {
--    signedTransaction  SignedTransaction,
--    encryptedTransaction    EncryptedData
--}


--NestedTransaction ::= SEQUENCE {
--    version         Version,
--    transaction     TransactionData,
    -- the hash of the transaction when encrypted
    -- this is here to validate that the onion encryption is being
    -- decrypted correctly through the various layers.
--    hash            SEQUENCE OF Hash
--}


END
