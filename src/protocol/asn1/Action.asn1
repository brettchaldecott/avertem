ActionModule DEFINITIONS AUTOMATIC TAGS ::= BEGIN
    IMPORTS Number, Version, Hash 
    FROM BasicModule
    Account 
    FROM AccountModule;

Action ::= SEQUENCE {
    version         Version,
    date            UTCTime,
    contract        Hash,
    contractName    UTF8String,
    parent          Hash,
    model           ANY
}

END
