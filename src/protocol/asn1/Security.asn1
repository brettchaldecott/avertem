SecurityModule DEFINITIONS AUTOMATIC TAGS ::= BEGIN
    IMPORTS Version, Hash
        FROM BasicModule;

Role ::= SEQUENCE {
    version         Version,
    id              Hash,
    name            UTF8String
}


END
