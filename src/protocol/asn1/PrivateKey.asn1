PrivateKeyModule DEFINITIONS AUTOMATIC TAGS ::= BEGIN
    IMPORTS Version, BerEncoding, EncryptedData
        FROM BasicModule;

PrivateKey ::= SEQUENCE {
    version         Version,
    -- the encrypted private key value
    key             EncryptedData
}


END
